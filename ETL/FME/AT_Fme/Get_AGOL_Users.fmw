FME workspace Get_AGOL_Users.fmw

Parameters:
- ENVIRONMENT = AGOL   # User Profile {PreProduction | Production}
- DestDataset_MSSQL_ADO = AT MSSQL - REPORTS PREPROD   # SQL Server Reporting Database Connection
- AGOL_USER = svcFME_ATGIS   # svcFME_ATGIS AGOL Username
- AGOL_PWD =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   # AGOL Password

Readers:
- CSV2_1: CSV2 from $(FME_MF_DIR)Data_Input_OrgChart\AT_OrgList.csv

Writers:
- MSSQL_ADO_1: MSSQL_ADO to $(DestDataset_MSSQL_ADO)

Note: Authors: Joseph Jose, Mike Oberdries | June 2018
Note: Append OrgList attributes / Join on email, User_Email / Supplier First = Yes
FeatureMerger_2
    SUPPLIERS_FIRST = Yes
    REJECT_NULL_MISSING_KEYS = No
    CONNECT_Z_MODE = First Wins
    MERGE_TYPE = Attributes Only
    GEOM_TYPE = Build Polygons
    IGNORE_NULLS = No
    ATTR_CONFLICT_RES = Use Requestor
    JOIN_KEYS = @UpperCase(@Value(email)) @UpperCase(@Value(User_Email)) AUTO
    PROCESS_DUPS = Yes
    ATTR_ACCUM_MODE = Merge Supplier
    MERGED -> SM_PREPRODPORTALUSAGELOGS (writer MSSQL_ADO_1)
    UNMERGED_REQUESTOR -> SM_PREPRODPORTALUSAGELOGS (writer MSSQL_ADO_1)
Note: SM_PREPRODPORTALUSAGELOGS [MSSQL_ADO] / Table Handling = Use Existing (retain history) / Non-Spatial
SM_PREPRODPORTALUSAGELOGS (writer MSSQL_ADO_1)
    attributes: Username varchar(25), Full_Name varchar(150), Created_Date datetime2, Modified_Date datetime2, Last_Login_Date datetime2, Collected_Date datetime2, User_Designation varchar(150), Org_Unit_Name varchar(200), User_Email varchar(150), Company_Area_Name varchar(250), Company_Division varchar(250), Company_Group varchar(250), Company_Department varchar(250), Company_Unit varchar(250), Company_Team varchar(250), Company_Subteam varchar(250), Environment varchar(50), Org_Unit varchar(100), Current_Organization varchar(250), Cost_Center integer, Cost_Center_Name integer, Employee_Group varchar(5), Employee_Group_Name varchar(250), Employee_Level integer, Employee_Level_Name varchar(250)

Bookmark: Iterate over AGOL users
Note: Initiate
Creator
    GEOMTYPE = Geometry Object
    NUM = 1
    CREATED -> AttributeManager
Note: Generate HTTP input attributes
AttributeManager
    ATTR_TABLE:
      REMOVE _creation_instance
      SET_TO _max_features = 100
      SET_TO _next_start = 1
      SET_TO _url_all_contend = https://atgis.maps.arcgis.com/sharing/rest/portals/self/users?returnPrivileges=true&f=json&start=@Value(_next_start)&num=@Value(_max_features)
      SET_TO _agol_user = $(AGOL_USER)
      SET_TO _agol_pwd = $(AGOL_PWD)
      SET_TO _url_generate_Token = https://www.arcgis.com/sharing/generateToken?username=@Value(_agol_user)&password=@Value(_agol_pwd)&referer=https%3A%2F%2Fwww.arcgis.com%2Fsharing&f=json
    -> HTTPCaller
Note: Generate Token
HTTPCaller
    CONNECTION_TIMEOUT_LENGTH = 60
    ERROR_ATTR = _error
    TARGET_URL = @Value(_url_generate_Token)
    TARGET_ATTR = _response_body
    HTTP_METHOD = GET
    USE_COOKIES = No
    STATUS_CODE_ATTR = _http_status_code
    FOLLOW_REDIRECTS = Yes
    TARGET_ATTR_ENCODING = auto-detect
    SAVE_FILE = Attribute
    TRANSFER_TIMEOUT_LENGTH = 90
    VERIFY_SSL_CERTIFICATES = Yes
    RESPONSE_HEADER_LIST_ATTR = _headers
    -> JSONFlattener
Note: Extract Attributes
JSONFlattener
    RECURSIVE = Yes
    JSON_DOCUMENT = @Value(_response_body)
    ERROR_LIST_ATTR = _json_error
    NEW_ATTRIBUTES = token
    -> Tester_2
Note: Is a valid response generated
Tester_2
    BOOL_OP = OR
    TEST_DESCRIPTION = ""
    TEST_MODE = Automatic
    TEST_CLAUSE = TEST token ATTRIBUTE_IS_MISSING ""
    PASSED -> Terminator_2
    FAILED -> LoopAGOLUsers
Note: Terminate Workspace
Terminator_2
    MESSAGE = ERROR: Invalid Response from HTTPCaller (AGOL)
Note: LOOPING / Loop over AGOL users
LoopAGOLUsers
    _NEXT_START = @Value(_next_start)
    _MAX_FEATURES = @Value(_max_features)
    _AGOL_PWD = @Value(_agol_pwd)
    TOKEN = @Value(token)
    _URL_AGOLUserJSON = https://atgis.maps.arcgis.com/sharing/rest/portals/self/users?returnPrivileges=true&f=json
    _AGOL_USER = @Value(_agol_user)
    -> FeatureHolder
Note: Hold loop output for / future processing
FeatureHolder
    -> AttributeKeeper

Bookmark: Parse and extract individual (unique) usernames
Note: Drop unwanted attributes
AttributeKeeper
    KEEP_ATTRS = Users
    -> Tester
Note: Test if valid output is obtained
Tester
    BOOL_OP = OR
    TEST_DESCRIPTION = ""
    TEST_MODE = Automatic
    TEST_CLAUSE = TEST Users ATTRIBUTE_IS_MISSING ""
    PASSED -> Terminator_3
    FAILED -> AttributeManager_2
Note: Prepare to split usernames
AttributeManager_2
    ATTR_TABLE:
      SET_TO _users_stripped_open = @ReplaceString(@Value(Users),"{","")
      SET_TO _users_stripped_close = @ReplaceString(@Value(_users_stripped_open),"}","#")
    -> AttributeSplitter
Note: Split out individual users
AttributeSplitter
    TRIM_OPTION = Both
    ATTR_NAME = _users_stripped_close
    DELIMITER = #
    DROP_EMPTY_PARTS = No
    LIST_NAME = _list_users
    -> ListExploder
Note: Explode _list_users{} attributes
ListExploder
    INDEX_ATTR = _element_index
    ATTR_ACCUM_MODE = Merge List Attributes
    LIST_ATTR = _list_users{}
    ATTR_CONFLICT_RES = Use List Attribute Values
    ELEMENTS -> AttributeKeeper_4
Note: Drop unwanted attributes
AttributeKeeper_4
    KEEP_ATTRS = _list_users
    -> AttributeManager_5
Note: Format individual users / as JSON notation
AttributeManager_5
    ATTR_TABLE = SET_TO _user_individual = {@Value(_list_users)}
    -> JSONFlattener_4
Note: Flatten JSON
JSONFlattener_4
    RECURSIVE = Yes
    JSON_DOCUMENT = @Value(_user_individual)
    ERROR_LIST_ATTR = _json_error
    NEW_ATTRIBUTES = username fullName firstName lastName email lastLogin created modified
    -> Tester_4
Note: Remove blanks in usernames
Tester_4
    BOOL_OP = OR
    TEST_DESCRIPTION = ""
    TEST_MODE = Automatic
    TEST_CLAUSE = TEST @Value(username) ATTRIBUTE_HAS_VALUE ""
    PASSED -> DuplicateFilter
Note: Remove duplicate usernames
DuplicateFilter
    KEYATTR = username
    INPUT_ORDERED_CHOICE = No
    UNIQUE -> AttributeManager_6
Note: Terminate Workspace
Terminator_3
    MESSAGE = ERROR: Invalid Response from HTTPCaller (AGOL)

Bookmark: Format attributes
Note: Format all the dates
AttributeManager_6
    ATTR_TABLE:
      RENAME_SET_VALUE username > Username
      RENAME_SET_VALUE fullName > Full_Name
      SET_TO _unix_epoch = 19700101
      SET_TO Created_Date = @Evaluate(@DateTimeAdd(@Value(_unix_epoch),PT@int(@Evaluate(@Value(created)/1000))S))
      SET_TO Modified_Date = @Evaluate(@DateTimeAdd(@Value(_unix_epoch),PT@int(@Evaluate(@Value(modified)/1000))S))
      SET_TO Last_Login_Date = @DateTimeAdd(@Value(_unix_epoch),PT@int(@Evaluate(@Value(lastLogin)/1000))S)
      SET_TO Collected_Date = @DateTimeNow()
      REMOVE created
      REMOVE modified
      SET_TO email = @LowerCase(@Value(email))
    -> AttributeKeeper_2
Note: Drop unwanted attributes
AttributeKeeper_2
    KEEP_ATTRS = firstName,_email_upper,Created_Date,Last_Login_Date,Modified_Date,Full_Name,Username,Collected_Date,email
    -> Sorter
Note: Sort on username
Sorter
    SORT_PARM = Username ALPHA ASCENDING
    SORTED -> AttributeCreator_2
Note: Set Environment as / $(ENVIRONMENT)
AttributeCreator_2
    ATTR_TABLE = SET_TO Environment = $(ENVIRONMENT)
    -> FeatureMerger_2 [REQUESTOR]

Bookmark: AT OrgList data
Note: AT_OrgList [CSV2]
CSV (reader CSV2_1)
    attributes: /BIC/ZUSRID string, /BIC/ZPONAME string, ORGUNIT string, /BIC/ZORGUNIT string, /BIC/ZCURRORG string, COSTCENTER string, /BIC/ZCCTEXT string, /BIC/ZEMAIL string, EMPLGROUP string, EMPLGROUPTXT string, /BIC/ZZPOSLVL string, /BIC/ZZPOSLVLN string, CO_AREA string, /BIC/ZDIVISION string, /BIC/ZGROUP string, /BIC/ZDEPT string, /BIC/ZUNIT string, /BIC/ZTEAM string, /BIC/ZSUBTEAM string
    -> AttributeManager_4
Note: Format attributes
AttributeManager_4
    ATTR_TABLE:
      SET_TO /BIC/ZUSRID = @UpperCase(@Value(/BIC/ZUSRID))
      RENAME_SET_VALUE /BIC/ZPONAME > User_Designation
      RENAME_SET_VALUE ORGUNIT > Org_Unit
      RENAME_SET_VALUE /BIC/ZORGUNIT > Org_Unit_Name
      RENAME_SET_VALUE /BIC/ZCURRORG > Current_Organization
      RENAME_SET_VALUE COSTCENTER > Cost_Center
      RENAME_SET_VALUE /BIC/ZCCTEXT > Cost_Center_Name
      RENAME_SET_VALUE /BIC/ZEMAIL > User_Email
      RENAME_SET_VALUE EMPLGROUP > Employee_Group
      RENAME_SET_VALUE EMPLGROUPTXT > Employee_Group_Name
      RENAME_SET_VALUE /BIC/ZZPOSLVL > Employee_Level
      RENAME_SET_VALUE /BIC/ZZPOSLVLN > Employee_Level_Name
      RENAME_SET_VALUE CO_AREA > Company_Area_Name
      RENAME_SET_VALUE /BIC/ZDIVISION > Company_Division
      RENAME_SET_VALUE /BIC/ZGROUP > Company_Group
      RENAME_SET_VALUE /BIC/ZDEPT > Company_Department
      RENAME_SET_VALUE /BIC/ZUNIT > Company_Unit
      RENAME_SET_VALUE /BIC/ZTEAM > Company_Team
      RENAME_SET_VALUE /BIC/ZSUBTEAM > Company_Subteam
      SET_TO Environment = $(ENVIRONMENT)
    -> FeatureMerger_2 [SUPPLIER]

FME custom transformer LoopAGOLUsers
iterateUsersAGO

Parameters:
- _URL_AGOLUserJSON = https://atgis.maps.arcgis.com/sharing/rest/portals/self/users?returnPrivileges=true&f=json   # URL_AGOLUserJSON
- _NEXT_START = @Value(_next_start)   # Next Start
- _MAX_FEATURES = @Value(_max_features)   # Max Features
- _AGOL_PWD = @Value(_agol_pwd)   # Agol Pwd
- _AGOL_USER = @Value(_agol_user)   # Agol User
- TOKEN = @Value(token)   # token

Bookmark: Iterate over AGOL users
INPUT (input)
    -> AttributeManager
Note: Configure HTTP arguments
AttributeManager
    ATTR_TABLE:
      SET_TO _url_All_Users = $(_URL_AGOLUserJSON)&num=100&start=@Value(_next_start)
      REMOVE _max_features
    -> HTTPCaller_3
Note: AGOL user list request / Max 100 features per request
HTTPCaller_3
    CONNECTION_TIMEOUT_LENGTH = 60
    ERROR_ATTR = _error
    TARGET_URL = @Value(_url_All_Users)&token=@Value(token)
    TARGET_ATTR = _response_body_AllUsers
    HTTP_METHOD = GET
    USE_COOKIES = No
    STATUS_CODE_ATTR = _http_status_code
    FOLLOW_REDIRECTS = Yes
    TARGET_ATTR_ENCODING = auto-detect
    AUTH_PASSWORD = $(_AGOL_PWD)
    AUTH_USERNAME = $(_AGOL_USER)
    SAVE_FILE = Attribute
    TRANSFER_TIMEOUT_LENGTH = 90
    AUTH_METHOD = NTLM
    VERIFY_SSL_CERTIFICATES = Yes
    RESPONSE_HEADER_LIST_ATTR = _headers
    -> JSONFlattener_3
Note: Flatten JSON response
JSONFlattener_3
    RECURSIVE = Yes
    JSON_DOCUMENT = @Value(_response_body_AllUsers)
    ERROR_LIST_ATTR = _json_error
    NEW_ATTRIBUTES = total start num nextStart
    -> Tester_2
Note: Is a valid response generated
Tester_2
    BOOL_OP = OR
    TEST_DESCRIPTION = ""
    TEST_MODE = Automatic
    TEST_CLAUSE = TEST total ATTRIBUTE_IS_MISSING ""
    PASSED -> Terminator_2
    FAILED -> JSONExtractor_2
Note: Get ALL users
JSONExtractor_2
    JSON_DOCUMENT = @Value(_response_body_AllUsers)
    EXTRACT_QUERY_TABLE = Users json["users"][*]
    EVALUATED -> AttributeKeeper_2
Note: Drop unwanted attributes
AttributeKeeper_2
    KEEP_ATTRS = nextStart,Users,token,_agol_pwd,_agol_user,_url_all_contend
    -> Tester
    -> OUTPUT (output)
OUTPUT (output)
Note: Test if there are more than / 100 users to be returned
Tester
    BOOL_OP = OR
    TEST_DESCRIPTION = ""
    TEST_MODE = Automatic
    TEST_CLAUSE = TEST @Value(nextStart) != -1
    PASSED -> AttributeManager_3
Note: Increment start_feature / to nextStart
AttributeManager_3
    ATTR_TABLE = SET_TO _next_start = @Value(nextStart)
    -> INPUT (output)
INPUT (output)
Note: Terminate Workspace
Terminator_2
    MESSAGE = ERROR: Invalid Response from HTTPCaller (AGOL)
