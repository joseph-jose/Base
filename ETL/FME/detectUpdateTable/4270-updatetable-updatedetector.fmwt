FME workspace 4270-updatetable-updatedetector.fmwt
Title: UpdateTable_UpdateDetector

Parameters:
- SourceDataset_MITAB = $(FME_MF_DIR)1/Downtown_Parks/Downtown_Parks.tab   # Source MapInfo TAB (MITAB) File(s)
- SourceDataset_POSTGIS_1 = fmedata   # Database
- DestDataset_POSTGIS_2 = fmedata   # Database

Readers:
- POSTGIS_1: POSTGIS from $(SourceDataset_POSTGIS_1)
- MITAB_1: MITAB from $(SourceDataset_MITAB)

Writers:
- POSTGIS_2: POSTGIS to $(DestDataset_POSTGIS_2)

Note: fmedata2015.Downtown_Parks: fmedata [POSTGIS]
fmedata2015.Downtown_Parks (reader POSTGIS_1)
    attributes: ParkId int2, RefParkId int2, ParkName char(40), NeighborhoodName char(40), EWStreet char(30), NSStreet char(30), DogPark char(1), Washrooms char(1), SpecialFeatures char(1)
    -> UpdateDetector [Original]
Note: Downtown_Parks: Downtown_Parks [MITAB]
Downtown_Parks (reader MITAB_1)
    attributes: ParkId smallint, RefParkId smallint, ParkName char(40), NeighborhoodName char(40), EWStreet char(30), NSStreet char(30), DogPark char(1), Washrooms char(1), SpecialFeatures char(1)
    -> UpdateDetector [Revised]
Note: fmedata2015.Downtown_Parks: fmedata [POSTGIS] - 2
Note: Feature Operation is set to fme_db_operation and Match Columns to ParkId. Setting Feature Operation to fme_db_operation means that the attribute value for fme_db_operation on the feature will guide whether the feature is inserted, updated or deleted in the database table. Match Columns ParkID is used to ensure the appropriate rows are updated or deleted in the database table.
fmedata2015.Downtown_Parks (writer POSTGIS_2)
    attributes: ParkId int2, RefParkId int2, ParkName char(40), NeighborhoodName char(40), EWStreet char(30), NSStreet char(30), DogPark char(1), Washrooms char(1), SpecialFeatures char(1)

Bookmark: Detect Changes
Note: Utilizing ParkID as the Key Attribute and selecting all Attribute(s) to match, the UpdateDetector will determine which features have been updated, inserted, unchanged or deleted in the revised MapInfo data.
UpdateDetector
    LENIENT_MATCH = no
    BLANK_AND_MISSING_DIFFER = No
    MATCH = 2D
    EXTRA_VERTEX_TOLERANCE = 0
    KEYATTR = ParkId
    MATCHATTRS = DogPark ParkId ParkName Washrooms RefParkId SpecialFeatures EWStreet NeighborhoodName NSStreet
    Updated -> AttributeCreator
    Deleted -> AttributeCreator_2

Bookmark: UPDATE
Note: Sets fme_db_operation to UPDATE, as it is necessary to update these features.
AttributeCreator
    ATTR_TABLE = SET_TO fme_db_operation = UPDATE
    -> fmedata2015.Downtown_Parks (writer POSTGIS_2)

Bookmark: DELETE
Note: Sets fme_db_operation to DELETE as this park is going to be redeveloped.
AttributeCreator_2
    ATTR_TABLE = SET_TO fme_db_operation = DELETE
    -> fmedata2015.Downtown_Parks (writer POSTGIS_2)

FME custom transformer UpdateDetector
This transformer is based on the ChangeDetector and extends its functionality by adding an Updated output port. It detects changes between two sets of input features.
One set of features enters the transformer via the Original port. The other set enters via the Revised port. Both sets must have a key attribute, which will be used to compare them against each other.
An Original feature is output via the Unchanged port when it is found to have matching key attribute and either matching geometry, matching attribute values, or both, with a feature in the Revised set.
An Original feature is output via the Deleted port when no key attribute match for it can be found in the Revised set.
A Revised feature with no key attribute match in the Original set is output via the Inserted port.
A Revised feature with key attribute match in the Original set and has changes either in geometry, or attribute values, or both, is output via the Updated port.
Inserted, updated and deleted features will have fme_db_operation set to INSERT, UPDATE or DELETE respectively.
Please note that to get correct results, the key attribute must be provided to both "Key Attribute" and "Attribute(s) to match" parameter prompts. 
Connect the transformer in your workspace and set the required parameters.
If Lenient Geometry Matching is set to yes then the order of points in line and area features will be ignored.
If Treat Blank Value as Different From Missing Attribute is Yes, then an attribute will be considered different for two features when one feature contains the attribute with a blank value and the other feature does not contain the attribute at all.
When geometry is being matched, Extra Vertex Tolerance can allow for extra vertices along line segments. A value of 0 means that no such extra vertices are permitted. A nonzero value controls how close any extra vertices must be to the line connecting the adjoining matching vertices. Note: This setting has no effect when using lenient geometry matching.

Parameters:
- KEYATTR =   # " " Key Attribute
- MATCH = 2D   # Match Geometry
- LENIENT_MATCH = no   # Lenient Geometry Matching
- MATCHATTRS =   # " " Attribute(s) to match
- BLANK_AND_MISSING_DIFFER = No   # Treat Blank Value as Different From Missing Attribute
- EXTRA_VERTEX_TOLERANCE = 0   # Extra Vertex Tolerance (optional)

Original (input)
    -> ATTRIBUTECREATOR
Note: Created by Dmitri Bagh / February 03, 2006 / dmitri.bagh@safe.com
Revised (input)
    -> ATTRIBUTECREATOR_2
Note: All parameters / are published / to match functionality / of ChangeDetector
Note: UPDATEDETECTOR
ChangeDetector
    MATCH_STRATEGY = Match Selected Attributes
    LENIENT_MATCH = $(LENIENT_MATCH)
    BLANK_AND_MISSING_DIFFER = $(BLANK_AND_MISSING_DIFFER)
    MATCH = $(MATCH)
    EXTRA_VERTEX_TOLERANCE = $(EXTRA_VERTEX_TOLERANCE)
    MATCHATTRS = $(MATCHATTRS)
    UNCHANGED -> ATTRIBUTEREMOVER_3
    ADDED -> Matcher_2
    DELETED -> Matcher
Updated (output)
Inserted (output)
Unchanged (output)
Deleted (output)

Bookmark: OrigFlag Creators
  Assigning OrigFlag Y for original 
  features and N for revised.
  For further use in testers 
  after Matcher 
  where original and revised 
  feaures can be merged together.
ATTRIBUTECREATOR: AttributeCreator
    ATTR_TABLE = SET_TO OrigFlag = Y
    -> ChangeDetector [ORIGINAL]
    -> Matcher_2
ATTRIBUTECREATOR_2: AttributeCreator
    ATTR_TABLE = SET_TO OrigFlag = N
    -> ChangeDetector [REVISED]
    -> Matcher

Bookmark: Matchers
  Here published Key Attribute
  distinguishes between added 
  and modified (above), 
  and - between deleted 
  and modified (below)
Matcher_2
    MATCH_STRATEGY = Match Selected Attributes
    LENIENT_MATCH = No
    BLANK_AND_MISSING_DIFFER = No
    MATCH = NONE
    CNT_ATTR = _match_id
    MATCHATTRS = $(KEYATTR)
    DIFFATTRS = OrigFlag
    MATCHED -> TESTER
    NOT_MATCHED -> TESTER_2
Matcher
    MATCH_STRATEGY = Match Selected Attributes
    LENIENT_MATCH = No
    BLANK_AND_MISSING_DIFFER = No
    MATCH = NONE
    CNT_ATTR = _match_id
    MATCHATTRS = $(KEYATTR)
    DIFFATTRS = OrigFlag
    NOT_MATCHED -> TESTER_3

Bookmark: Testers
  For updated and added 
  we keep revised features
  For deleted - original features
TESTER: Tester
    TEST_LIST = &OrigFlag,=,N
    BOOL_OP = OR
    TEST_CLAUSE = TEST @Value(OrigFlag) = N
    TEST_DESCRIPTION = ""
    TEST_MODE = Automatic
    PASSED -> ATTRIBUTEREMOVER
TESTER_2: Tester
    TEST_LIST = &OrigFlag,=,N
    BOOL_OP = OR
    TEST_CLAUSE = TEST @Value(OrigFlag) = N
    TEST_DESCRIPTION = ""
    TEST_MODE = Automatic
    PASSED -> ATTRIBUTEREMOVER_2
TESTER_3: Tester
    TEST_LIST = &OrigFlag,=,Y
    BOOL_OP = OR
    TEST_CLAUSE = TEST @Value(OrigFlag) = Y
    TEST_DESCRIPTION = ""
    TEST_MODE = Automatic
    PASSED -> ATTRIBUTEREMOVER_4

Bookmark: Deleting temp attributes
ATTRIBUTEREMOVER: AttributeRemover
    REMOVE_ATTRS = _match_id,OrigFlag
    -> AttributeCreator
ATTRIBUTEREMOVER_2: AttributeRemover
    REMOVE_ATTRS = _match_id,OrigFlag
    -> AttributeCreator_2
ATTRIBUTEREMOVER_3: AttributeRemover
    REMOVE_ATTRS = OrigFlag
    -> Unchanged (output)
ATTRIBUTEREMOVER_4: AttributeRemover
    REMOVE_ATTRS = _match_id,OrigFlag
    -> AttributeCreator_3

Bookmark: Add fme_db_operation attribute
AttributeCreator
    ATTR_TABLE = SET_TO fme_db_operation = UPDATE
    -> Updated (output)
AttributeCreator_2
    ATTR_TABLE = SET_TO fme_db_operation = INSERT
    -> Inserted (output)
AttributeCreator_3
    ATTR_TABLE = SET_TO fme_db_operation = DELETE
    -> Deleted (output)
