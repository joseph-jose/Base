FME workspace 4556-992-writeupdatestoagol.fmw

Parameters:
- ARCGISONLINEFEATURES_IN_USER_ARCGISONLINEFEATURES =   # User
- ARCGISONLINEFEATURES_IN_PASSWORD_ARCGISONLINEFEATURES =   # Password
- SourceDataset_XML = http://webservices.nextbus.com/service/publicXMLFeed?command=vehicleLocations&a=sf-muni&r=N&t=0   # Source XML File(s)

Readers:
- XML_1: XML from $(SourceDataset_XML) in LL84
- ARCGISONLINEFEATURES_1: ARCGISONLINEFEATURES from www.arcgis.com

Writers:
- ARCGISONLINEFEATURES_2: ARCGISONLINEFEATURES to www.arcgis.com

Bookmark: 1. Read Sources
Note: Read from existing ArcGIS / Online feature layer
Buses (reader ARCGISONLINEFEATURES_1)
    attributes: FID esriFieldTypeInteger, SECSSINCER esriFieldTypeDouble, ID esriFieldTypeDouble, ROUTETAG esriFieldTypeString(20), PREDICTABL esriFieldTypeString(20), SPEEDKMHR esriFieldTypeDouble, DIRTAG esriFieldTypeString(20), HEADING esriFieldTypeDouble
    -> FeatureMerger [REQUESTOR]
Note: New Bus information
vehicle (reader XML_1)
    attributes: vehicle.dirTag xml_char(7), vehicle.heading xml_decimal(4,0), vehicle.id xml_decimal(5,0), vehicle.lat xml_decimal(10,7), vehicle.leadingVehicleId xml_decimal(5,0), vehicle.lon xml_decimal(10,5), vehicle.predictable xml_char(6), vehicle.routeTag xml_char(2), vehicle.secsSinceReport xml_decimal(3,0), vehicle.speedKmHr xml_decimal(18,15), xml_fragment xml_xml, xml_id xml_char(16), xml_matched_element xml_char(8)
    -> BulkAttributeRenamer

Bookmark: Modify XML feed to match feature layer data structure
BulkAttributeRenamer
    REPLACE_STR = vehicle.
    ATTRCHOICE = All Attributes
    PATTERN_ACTION_DISP = Remove Prefix String
    CASE_DISP = yes
    -> BulkAttributeRenamer_2
BulkAttributeRenamer_2
    ATTRCHOICE = All Attributes
    PATTERN_ACTION_DISP = Change Case
    CASE_CHANGE_TYPE = UPPERCASE
    -> VertexCreator
Note: Create point geometries / with current location
VertexCreator
    XVAL = @Value(LON)
    MODE_NAME = Add Point
    YVAL = @Value(LAT)
    -> FeatureMerger [SUPPLIER]

Bookmark: 2. Check for Updates
Note: Adds FID attribute to features / that already exist in the Feature / Service.
FeatureMerger
    IGNORE_NULLS = No
    ATTR_CONFLICT_RES = Use Supplier
    ATTR_ACCUM_MODE = Merge Supplier
    JOIN_KEYS = @Value(ID) @Value(ID) AUTO
    PROCESS_DUPS = No
    MERGE_TYPE = Attributes and Geometry
    SUPPLIERS_FIRST = No
    REJECT_NULL_MISSING_KEYS = No
    MERGED -> AttributeCreator
    NOT_MERGED -> AttributeCreator_2
    UNREFERENCED -> AttributeCreator_3

Bookmark: 3. Set Writer Action
Note: Tag as UPDATE
AttributeCreator
    ATTR_LIST = fme_db_operation,UPDATE
    -> Buses (writer ARCGISONLINEFEATURES_2)
Note: Tag as DELETE
AttributeCreator_2
    ATTR_LIST = fme_db_operation,DELETE
    -> Buses (writer ARCGISONLINEFEATURES_2)
Note: Tag as INSERT
AttributeCreator_3
    ATTR_LIST = fme_db_operation,INSERT
    -> Buses (writer ARCGISONLINEFEATURES_2)

Bookmark: 4. Send Features to Writer
  This writer is in update mode, so will check the FID on each of the features
  sent here and will update, insert or delete the corresponding one in the existing layer
Buses (writer ARCGISONLINEFEATURES_2)
    attributes: FID esriFieldTypeInteger, SECSSINCER esriFieldTypeDouble, ID esriFieldTypeDouble, ROUTETAG esriFieldTypeString(20), PREDICTABL esriFieldTypeString(20), SPEEDKMHR esriFieldTypeDouble, DIRTAG esriFieldTypeString(20), HEADING esriFieldTypeDouble
