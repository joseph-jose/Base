FME workspace 4052-createtable-downtown-parks.fmw

Parameters:
- SourceDataset_POSTGIS_1 = fmedata   # Database
- DestDataset_POSTGIS_2 = fmedata   # Database

Readers:
- POSTGIS_1: POSTGIS from $(SourceDataset_POSTGIS_1)

Writers:
- POSTGIS_2: POSTGIS to $(DestDataset_POSTGIS_2)

fmedata2015.Parks (reader POSTGIS_1)
    attributes: ParkId int2, RefParkId int2, ParkName char(40), NeighborhoodName char(40), EWStreet char(30), NSStreet char(30), DogPark char(1), Washrooms char(1), SpecialFeatures char(1)
    -> Tester_2
Tester_2
    TEST_DESCRIPTION = ""
    BOOL_OP = OR
    TEST_CLAUSE = TEST @Value(NeighborhoodName) = Downtown
    TEST_MODE = Automatic
    PASSED -> fmedata2015.Downtown_Parks (writer POSTGIS_2)
Note: fmedata2015.Downtown_Parks: PostGIS Training Database [POSTGIS] - 2 / Under the Format Parameters, Feature Operation is set to INSERT and Table Handling is set to DROP and CREATE, which means a new Downtown_Parks table will be created when the workspace is run.
fmedata2015.Downtown_Parks (writer POSTGIS_2)
    attributes: ParkId int2, RefParkId int2, ParkName char(40), NeighborhoodName char(40), EWStreet char(30), NSStreet char(30), DogPark char(1), Washrooms char(1), SpecialFeatures char(1)
