FME workspace Get_Portal_Users.fmw

Parameters:
- PORTAL_USER_DETAILS_URL = https://atalgispsp01.aucklandtransport.govt.nz/arcgis/sharing/rest/community/users/   # PORTAL URL to return User Details
- ENVIRONMENT = PRODUCTION   # User Profile {PreProduction | Production}
- DestDataset_MSSQL_ADO = AT MSSQL - REPORTS PREPROD   # SQL Server Reporting Database Connection
- PORTAL_USER = svc_fme_gis   # svc_fme_gis PORTAL Username
- PORTAL_PWD =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   # PORTAL Password

Readers:
- CSV2_1: CSV2 from $(FME_MF_DIR)Data_Input_OrgChart\AT_OrgList.csv

Writers:
- MSSQL_ADO_1: MSSQL_ADO to $(DestDataset_MSSQL_ADO)

Note: Authors: Joseph Jose, Mike Oberdries | May 2018
Note: Sort on Username
Sorter
    SORT_PARM = Username ALPHA ASCENDING
    SORTED -> AttributeManager_12
Note: Format Username / Create_username_join
AttributeManager_12
    ATTR_TABLE:
      SET_TO Username = @ReplaceString(@Value(Username),"@TRANSPORT","")
      SET_TO _username_join = @UpperCase(@Value(Username))
      SET_TO Environment = $(ENVIRONMENT)
    -> FeatureMerger_2 [REQUESTOR]
Note: Append OrgList attributes / Join on _username_join, /BIC/ZUSRID / Supplier First = Yes
FeatureMerger_2
    IGNORE_NULLS = No
    ATTR_CONFLICT_RES = Use Requestor
    MERGE_TYPE = Attributes Only
    REJECT_NULL_MISSING_KEYS = No
    PROCESS_DUPS = No
    SUPPLIERS_FIRST = Yes
    JOIN_KEYS = @Value(_username_join) @Value(/BIC/ZUSRID) AUTO
    ATTR_ACCUM_MODE = Merge Supplier
    MERGED -> SM_PREPRODPORTALUSAGELOGS (writer MSSQL_ADO_1)
    UNMERGED_REQUESTOR -> Tester
Note: Drop default ESRI* usernames / Service accounts go forward
Tester
    TEST_MODE = Automatic
    TEST_DESCRIPTION = ""
    BOOL_OP = AND
    TEST_CLAUSE = TEST @Value(_username_join) BEGINS_WITH ESRI
    FAILED -> SM_PREPRODPORTALUSAGELOGS (writer MSSQL_ADO_1)
Note: SM_PREPRODPORTALUSAGELOGS [MSSQL_ADO] / Table Handling = Use Existing (retain history) / Non-Spatial
SM_PREPRODPORTALUSAGELOGS (writer MSSQL_ADO_1)
    attributes: Username varchar(25), Full_Name varchar(150), Created_Date datetime2, Modified_Date datetime2, Last_Login_Date datetime2, Collected_Date datetime2, User_Designation varchar(150), Org_Unit_Name varchar(200), User_Email varchar(150), Company_Area_Name varchar(250), Company_Division varchar(250), Company_Group varchar(250), Company_Department varchar(250), Company_Unit varchar(250), Company_Team varchar(250), Company_Subteam varchar(250), Environment varchar(50), Org_Unit varchar(100), Current_Organization varchar(250), Cost_Center integer, Cost_Center_Name varchar(250), Employee_Group varchar(5), Employee_Group_Name varchar(250), Employee_Level integer, Employee_Level_Name varchar(250)

Bookmark: Create a feature for each letter of the Alphabet
Note: Initiator
Creator
    GEOMTYPE = Geometry Object
    NUM = 1
    CREATED -> AttributeManager_2
AttributeManager_2
    ATTR_TABLE = SET_TO _list_items = A,B,C,D,E,F,G,H,I,J,K,L,M,N,O,P,Q,R,S,T,U,V,W,X,Y,Z
    -> AttributeSplitter_3
AttributeSplitter_3
    ATTR_NAME = _list_items
    DELIMITER = ,
    LIST_NAME = _list_alphabet
    DROP_EMPTY_PARTS = No
    TRIM_OPTION = Both
    -> ListExploder_2
ListExploder_2
    INDEX_ATTR = _element_index
    LIST_ATTR = _list_alphabet{}
    ATTR_CONFLICT_RES = Use List Attribute Values
    ATTR_ACCUM_MODE = Merge List Attributes
    ELEMENTS -> AttributeKeeper
AttributeKeeper
    KEEP_ATTRS = _element_index,_list_alphabet
    -> AttributeManager

Bookmark: ArcGIS PORTAL API User Request - Iterate 100 Records at a Time
Note: Configure arguments to pass
AttributeManager
    ATTR_TABLE:
      SET_TO _name_begins_with = @Value(_list_alphabet)*
      SET_TO _start_feature = 1
      SET_TO _return_feature = 100
      SET_TO _target_url
      REMOVE _list_alphabet
      REMOVE _element_index
    -> LoopPortalUser
Note: LOOPING / Loop over AGOL users
LoopPortalUser
    _START_FEATURE = @Value(_start_feature)
    PORTAL_PWD =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
    PORTAL_USERS_URL = https://atalgispsp01.aucklandtransport.govt.nz/arcgis/sharing/rest/community/users?f=pjson&sortField=&sortOrder=
    PORTAL_USER = svc_fme_gis
    _TARGET_URL = @Value(_target_url)
    _RETURN_FEATURE = @Value(_return_feature)
    _NAME_BEGINS_WITH = @Value(_name_begins_with)
    -> FeatureHolder
Note: Hold features
FeatureHolder
    -> AttributeKeeper_8
Note: Drop unwanted attributes
AttributeKeeper_8
    KEEP_ATTRS = _name_begins_with,Users,nextStart
    -> AttributeKeeper_9

Bookmark: Parse and extract individual (unique) usernames
Note: Drop unwanted attributes
AttributeKeeper_9
    KEEP_ATTRS = Users
    -> AttributeManager_4
Note: Prepare to split usernames
AttributeManager_4
    ATTR_TABLE:
      SET_TO _users_stripped_open = @ReplaceString(@Value(Users),"{","")
      SET_TO _users_stripped_close = @ReplaceString(@Value(_users_stripped_open),"}","#")
    -> AttributeSplitter
Note: Split individual users
AttributeSplitter
    ATTR_NAME = _users_stripped_close
    DELIMITER = #
    LIST_NAME = _list_users
    DROP_EMPTY_PARTS = No
    TRIM_OPTION = Both
    -> ListExploder
Note: Explode our list of attributes
ListExploder
    INDEX_ATTR = _element_index
    LIST_ATTR = _list_users{}
    ATTR_CONFLICT_RES = Use List Attribute Values
    ATTR_ACCUM_MODE = Merge List Attributes
    ELEMENTS -> AttributeKeeper_4
Note: Remove unwanted attributes
AttributeKeeper_4
    KEEP_ATTRS = _list_users
    -> AttributeManager_5
Note: Format individual users / as JSON notation
AttributeManager_5
    ATTR_TABLE = SET_TO _user_individual = {@Value(_list_users)}
    -> JSONFlattener_4
Note: Flatten JSON
JSONFlattener_4
    NEW_ATTRIBUTES = username fullName created modified
    RECURSIVE = Yes
    JSON_DOCUMENT = @Value(_user_individual)
    ERROR_LIST_ATTR = _json_error
    -> Tester_4
Note: Remove blanks in usernames
Tester_4
    TEST_MODE = Automatic
    TEST_DESCRIPTION = ""
    BOOL_OP = OR
    TEST_CLAUSE = TEST @Value(username) ATTRIBUTE_HAS_VALUE ""
    PASSED -> AttributeKeeper_5
Note: Remove unwanted attributes
AttributeKeeper_5
    KEEP_ATTRS = username,created,modified,fullName
    -> DuplicateFilter
Note: Remove duplicate usernames
DuplicateFilter
    KEYATTR = username
    INPUT_ORDERED_CHOICE = No
    UNIQUE -> AttributeManager_6

Bookmark: Call individual username information and extract details
Note: Configure HTTP url and / url arguments
AttributeManager_6
    ATTR_TABLE:
      RENAME_SET_VALUE username > Username
      RENAME_SET_VALUE fullName > Full_Name
      SET_TO _unix_epoch = 19700101
      SET_TO Created_Date = @Evaluate(@DateTimeAdd(@Value(_unix_epoch),PT@int(@Evaluate(@Value(created)/1000))S))
      SET_TO Modified_Date = @Evaluate(@DateTimeAdd(@Value(_unix_epoch),PT@int(@Evaluate(@Value(modified)/1000))S))
      SET_TO Last_Login_Date = @DateTimeNow()
      SET_TO Collected_Date = @DateTimeNow()
      SET_TO _username_url = @ReplaceString(@Value(Username),"@","%40")
      SET_TO _target_url = $(PORTAL_USER_DETAILS_URL)@Value(_username_url)
      REMOVE created
      REMOVE modified
    -> HTTPCaller_4
Note: Portal username details request
HTTPCaller_4
    AUTH_METHOD = NTLM
    HTTP_METHOD = GET
    STATUS_CODE_ATTR = _http_status_code
    TRANSFER_TIMEOUT_LENGTH = 90
    USE_COOKIES = No
    AUTH_USERNAME = $(PORTAL_USER)
    TARGET_ATTR = _response_body
    AUTH_PASSWORD = $(PORTAL_PWD)
    TARGET_URL = @Value(_target_url)
    VERIFY_SSL_CERTIFICATES = Yes
    ERROR_ATTR = _error
    CONNECTION_TIMEOUT_LENGTH = 60
    SAVE_FILE = Attribute
    TARGET_ATTR_ENCODING = auto-detect
    RESPONSE_HEADER_LIST_ATTR = _headers
    FOLLOW_REDIRECTS = Yes
    -> HTMLExtractor
Note: Extract the HTML / for each JSON url
HTMLExtractor
    RESULT_TYPE_NAME = FIRST_MATCH
    HTML_FIELD = @Value(_response_body)
    SEARCH_TABLE = table .formTable Value
    HTML_SPECIFICATION = Content
    Results -> AttributeManager_7
Note: Extract the table segment / from the HTML
AttributeManager_7
    ATTR_TABLE:
      SET_TO _table_stripped = @ReplaceString(@ReplaceString(@ReplaceString(@ReplaceString(@ReplaceString(@ReplaceString(@ReplaceString(@ReplaceString(@Value(table),"</tr>",";"),"<tr>",""),"<td>",""),"</td>","")," ",""),"\r",""),"\r\n",""),"<trvalign=""top"">","")
      REMOVE _unix_epoch
    -> AttributeSplitter_2
Note: Create a list of attributes / from the table
AttributeSplitter_2
    ATTR_NAME = _table_stripped
    DELIMITER = ;
    LIST_NAME = _list_table_elements
    DROP_EMPTY_PARTS = Yes
    TRIM_OPTION = Both
    -> ListElementCounter
Note: Count list of items
ListElementCounter
    LIST_NAME = _list_table_elements{}
    CNT_ATTR = _count_list
    -> Tester_5
Note: Filter / _count_list > 13
Tester_5
    TEST_MODE = Automatic
    TEST_DESCRIPTION = ""
    BOOL_OP = OR
    TEST_CLAUSE = TEST @Value(_count_list) > 13
    PASSED -> AttributeManager_11
    FAILED -> AttributeManager_8
Note: Extract attributes / of interest
AttributeManager_11
    ATTR_TABLE:
      SET_TO _List_idxLastLogin = @Evaluate(@Value(_count_list)-3)
      SET_TO _List_idxModified = @Evaluate(@Value(_count_list)-4)
      SET_TO Last_Login_Date = @ReplaceString(@Value(_list_table_elements{@Value(_List_idxLastLogin)}),"LastLogin:","")
    -> AttributeKeeper_6
Note: Extract attributes / of interest
AttributeManager_8
    ATTR_TABLE:
      SET_TO _List_idxLastLogin = @Evaluate(@Value(_count_list)-2)
      SET_TO _List_idxModified = @Evaluate(@Value(_count_list)-3)
      SET_TO Last_Login_Date = @ReplaceString(@Value(_list_table_elements{@Value(_List_idxLastLogin)}),"LastLogin:","")
    -> AttributeKeeper_6
Note: Remove unwanted attributes
AttributeKeeper_6
    KEEP_ATTRS = Username,Full_Name,Collected_Date,Created_Date,Modified_Date,Last_Login_Date
    -> AttributeManager_9
Note: Drop unwanted HTML tags
AttributeManager_9
    -> StringReplacer
Note: Remove line feed in / extracted values
StringReplacer
    FIND_TEXT = "\n"
    CASE = NO
    REGEXP = NO
    SRC_ATTRS = Last_Login_Date
    NO_MATCH = _FME_NO_OP_
    -> Tester_2
Note: Filter / Last_Login_date = N/A
Tester_2
    TEST_MODE = Automatic
    TEST_DESCRIPTION = ""
    BOOL_OP = OR
    TEST_CLAUSE = TEST @Value(Last_Login_Date) = N/A
    PASSED -> AttributeManager_10
    FAILED -> DateTimeConverter
Note: Assign N/A as NULL
AttributeManager_10
    ATTR_TABLE = SET_TO Last_Login_Date = FME_NULL_VALUE
    -> DateTimeConverter_3
Note: Format Dates / ** exclude Collected_Date
DateTimeConverter
    OUT_FORMAT = %Y%m%d
    REPAIR_INPUT = NO
    IN_FORMAT = %d/%m/%Y
    DATETIME_ATTR = Last_Login_Date
    -> DateTimeConverter_3
Note: Format Collected_Date
DateTimeConverter_3
    OUT_FORMAT = %Y%m%d
    REPAIR_INPUT = NO
    IN_FORMAT = %Y%m%d%H%M%S$
    DATETIME_ATTR = Collected_Date
    -> Sorter

Bookmark: AT OrgList data
Note: AT_OrgList [CSV2]
CSV (reader CSV2_1)
    attributes: /BIC/ZUSRID string, /BIC/ZPONAME string, ORGUNIT string, /BIC/ZORGUNIT string, /BIC/ZCURRORG string, COSTCENTER string, /BIC/ZCCTEXT string, /BIC/ZEMAIL string, EMPLGROUP string, EMPLGROUPTXT string, /BIC/ZZPOSLVL string, /BIC/ZZPOSLVLN string, CO_AREA string, /BIC/ZDIVISION string, /BIC/ZGROUP string, /BIC/ZDEPT string, /BIC/ZUNIT string, /BIC/ZTEAM string, /BIC/ZSUBTEAM string
    -> AttributeManager_13
Note: Format attributes
AttributeManager_13
    ATTR_TABLE:
      SET_TO /BIC/ZUSRID = @UpperCase(@Value(/BIC/ZUSRID))
      RENAME_SET_VALUE /BIC/ZPONAME > User_Designation
      RENAME_SET_VALUE ORGUNIT > Org_Unit
      RENAME_SET_VALUE /BIC/ZORGUNIT > Org_Unit_Name
      RENAME_SET_VALUE /BIC/ZCURRORG > Current_Organization
      RENAME_SET_VALUE COSTCENTER > Cost_Center
      RENAME_SET_VALUE /BIC/ZCCTEXT > Cost_Center_Name
      RENAME_SET_VALUE /BIC/ZEMAIL > User_Email
      RENAME_SET_VALUE EMPLGROUP > Employee_Group
      RENAME_SET_VALUE EMPLGROUPTXT > Employee_Group_Name
      RENAME_SET_VALUE /BIC/ZZPOSLVL > Employee_Level
      RENAME_SET_VALUE /BIC/ZZPOSLVLN > Employee_Level_Name
      RENAME_SET_VALUE CO_AREA > Company_Area_Name
      RENAME_SET_VALUE /BIC/ZDIVISION > Company_Division
      RENAME_SET_VALUE /BIC/ZGROUP > Company_Group
      RENAME_SET_VALUE /BIC/ZDEPT > Company_Department
      RENAME_SET_VALUE /BIC/ZUNIT > Company_Unit
      RENAME_SET_VALUE /BIC/ZTEAM > Company_Team
      RENAME_SET_VALUE /BIC/ZSUBTEAM > Company_Subteam
      SET_TO Environment = $(ENVIRONMENT)
    -> FeatureMerger_2 [SUPPLIER]

FME custom transformer LoopPortalUser
IterateUsersPortal

Parameters:
- _TARGET_URL = @Value(_target_url)   # Target Url
- _NAME_BEGINS_WITH = @Value(_name_begins_with)   # Name Begins With
- PORTAL_USERS_URL = https://atalgispsp01.aucklandtransport.govt.nz/arcgis/sharing/rest/community/users?f=pjson&sortField=&sortOrder=   # PORTAL URL to return List of Users
- _RETURN_FEATURE = @Value(_return_feature)   # Return Feature
- _START_FEATURE = @Value(_start_feature)   # Start Feature
- PORTAL_USER = svc_fme_gis   # svc_fme_gis PORTAL Username
- PORTAL_PWD =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   # PORTAL Password

Bookmark: Iterate over Portal Users
INPUT (input)
    -> AttributeManager_2
Note: Configure HTTP arguments
AttributeManager_2
    ATTR_TABLE = SET_TO _target_url = $(PORTAL_USERS_URL)&q=@Value(_name_begins_with)&start=@Value(_start_feature)&num=@Value(_return_feature)
    -> AttributeKeeper_7
Note: Drop unwanted attributes
AttributeKeeper_7
    KEEP_ATTRS = _target_url,_name_begins_with
    -> HTTPCaller_3
Note: ArcGIS Portal user list request / Max 100 features per request
HTTPCaller_3
    AUTH_METHOD = NTLM
    HTTP_METHOD = GET
    STATUS_CODE_ATTR = _http_status_code
    TRANSFER_TIMEOUT_LENGTH = 90
    USE_COOKIES = No
    AUTH_USERNAME = $(PORTAL_USER)
    TARGET_ATTR = _response_body_all_users
    AUTH_PASSWORD = $(PORTAL_PWD)
    TARGET_URL = @Value(_target_url)
    VERIFY_SSL_CERTIFICATES = Yes
    ERROR_ATTR = _error
    CONNECTION_TIMEOUT_LENGTH = 60
    SAVE_FILE = Attribute
    TARGET_ATTR_ENCODING = auto-detect
    RESPONSE_HEADER_LIST_ATTR = _headers
    FOLLOW_REDIRECTS = Yes
    -> JSONFlattener_3
Note: Flatten JSON response
JSONFlattener_3
    NEW_ATTRIBUTES = total start num nextStart
    RECURSIVE = Yes
    JSON_DOCUMENT = @Value(_response_body_all_users)
    ERROR_LIST_ATTR = _json_error
    -> Tester_2
Note: Is a valid response generated
Tester_2
    TEST_MODE = Automatic
    TEST_DESCRIPTION = ""
    BOOL_OP = OR
    TEST_CLAUSE = TEST total ATTRIBUTE_IS_MISSING ""
    PASSED -> Terminator
    FAILED -> JSONExtractor_2
Note: Extract ALL users
JSONExtractor_2
    JSON_DOCUMENT = @Value(_response_body_all_users)
    EXTRACT_QUERY_TABLE = Users json["results"][*]
    EVALUATED -> AttributeKeeper_2
Note: Drop unwanted attributes
AttributeKeeper_2
    KEEP_ATTRS = total,num,Users,_name_begins_with,nextStart
    -> Tester
    -> OUTPUT (output)
OUTPUT (output)
Note: Test if there are more than / 100 users to be returned
Tester
    TEST_MODE = Automatic
    TEST_DESCRIPTION = ""
    BOOL_OP = OR
    TEST_CLAUSE = TEST @Value(nextStart) < 0
    FAILED -> AttributeManager
Note: Increment start_feature / to nextStart
AttributeManager
    ATTR_TABLE:
      SET_TO _target_url = $(PORTAL_USERS_URL)&q=@Value(_name_begins_with)&start=@Value(nextStart)&num=100
      SET_TO _return_feature = 100
      SET_TO _start_feature = @Value(nextStart)
    -> AttributeKeeper
Note: Drop unwanted attributes
AttributeKeeper
    KEEP_ATTRS = _target_url,_start_feature,_name_begins_with,_return_feature
    -> INPUT (output)
INPUT (output)
Note: Terminate Workspace
Terminator
    MESSAGE = ERROR: Invalid Response from HTTPCaller (ArcGIS Portal)
