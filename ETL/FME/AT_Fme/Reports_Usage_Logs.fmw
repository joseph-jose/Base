FME workspace Reports_Usage_Logs.fmw

Parameters:
- DestDataset_XLSXW = $(OutputPath)\UserUsageLogs_$(GISServer)_$(EndDate).xlsx   # Destination Microsoft Excel File
- OutputPath = $(FME_MF_DIR)Data_Output_Reporting
- StartDate = 20180412   # "{}" StartDate
- EndDate = 20180703   # "{}" EndDate
- GISServer = PREPRODUCTION
- ENVIRONMENT = AGOL   # User Profile {PreProduction | Production}

Readers:
- CSV2_1: CSV2 from $(FME_MF_DIR)Data_Input_OrgChart\AT_OrgList.csv

Writers:
- XLSXW_1: XLSXW to $(DestDataset_XLSXW)

Bookmark: SQL for Reports
Note: Get LastLogin by User
SQLCreator
    SQL_STATEMENT:
      select username, format(Last_Login_Date, 'dd/MM/yyyy') as LastLoginDate from
      (
      select distinct(username),  max(Last_Login_Date) as Last_Login_Date from [SM_PREPRODPORTALUSAGELOGS]
      where [Environment]='$(GISServer)'
      group by username
      ) as A ORDER BY Last_Login_Date DESC
    MSSQL_ADO_QUERY_FEATURE_TYPES_FOR_MERGE_FILTERS = Yes
    EXPOSED_ATTRIBUTE_LIST = username,LastLoginDate
    MSSQL_ADO_COMMAND_TIMEOUT = 30
    MSSQL_ADO_NAMED_CONNECTION = AT MSSQL - REPORTS PREPROD
    DATASET = AT MSSQL - REPORTS PREPROD
    FORMAT = MSSQL_ADO
    RESULT -> LastLoginsByUser (writer XLSXW_1)
LastLoginsByUser (writer XLSXW_1)
    attributes: username auto(20), LastLoginDate datetime(20)
Note: LastCount by User
SQLCreator_3
    SQL_STATEMENT:
      select distinct(username), Full_Name, count(*) as TotalLogins from
      (
      SELECT distinct(username), Full_Name, Last_Login_Date
      FROM [SM_PREPRODPORTALUSAGELOGS] where
      Last_Login_Date between convert(date, '$(StartDate)', 112)  and convert(date, '$(EndDate)', 112)
      and [Environment]='$(GISServer)'
      ) A
      group by username, Full_Name
    MSSQL_ADO_QUERY_FEATURE_TYPES_FOR_MERGE_FILTERS = Yes
    EXPOSED_ATTRIBUTE_LIST = username,Full_Name,TotalLogins
    MSSQL_ADO_COMMAND_TIMEOUT = 30
    MSSQL_ADO_NAMED_CONNECTION = AT MSSQL - REPORTS PREPROD
    DATASET = AT MSSQL - REPORTS PREPROD
    FORMAT = MSSQL_ADO
    RESULT -> LastCountsByUser (writer XLSXW_1)
LastCountsByUser (writer XLSXW_1)
    attributes: username auto(20), Full_Name auto(20), TotalLogins auto(20)
Note: Logins User Weekly
SQLCreator_4
    SQL_STATEMENT:
      select distinct(username), Full_Name, datepart(week, Last_Login_Date) as YearOfWeek,
      dateadd (week, datepart(week, Last_Login_Date), dateadd (year, year(getdate())-1900, 0)) - 4 - datepart(dw, dateadd (week, datepart(week, Last_Login_Date), dateadd (year, year(getdate())-1900, 0)) - 4) + 1 as WeekStart,
      dateadd (week, datepart(week, Last_Login_Date), dateadd (year, year(getdate())-1900, 0)) - 4 - datepart(dw, dateadd (week, datepart(week, Last_Login_Date), dateadd (year, year(getdate())-1900, 0)) - 4) + 1 + 7  as WeekEnd,
      count(*) LoginsPerWeek from
      (
      SELECT distinct(username), Full_Name, Last_Login_Date
      FROM [SM_PREPRODPORTALUSAGELOGS] where
      Last_Login_Date between convert(date, '$(StartDate)', 112) and convert(date, '$(EndDate)', 112)
      and [Environment]='$(GISServer)'
      ) A
      group by username, Full_Name, datepart(week, Last_Login_Date)
      order by datepart(week, Last_Login_Date) desc, Full_Name
    MSSQL_ADO_QUERY_FEATURE_TYPES_FOR_MERGE_FILTERS = Yes
    EXPOSED_ATTRIBUTE_LIST = username,Full_Name,YearOfWeek,WeekStart,WeekEnd,LoginsPerWeek
    MSSQL_ADO_COMMAND_TIMEOUT = 30
    MSSQL_ADO_NAMED_CONNECTION = AT MSSQL - REPORTS PREPROD
    DATASET = AT MSSQL - REPORTS PREPROD
    FORMAT = MSSQL_ADO
    RESULT -> AttributeManager_2
AttributeManager_2
    ATTR_TABLE:
      SET_TO WeekStart = @DateTimeFormat(@Value(WeekStart),%d/%m/%Y)

      SET_TO WeekEnd = @DateTimeFormat(@Value(WeekEnd),%d/%m/%Y)
    -> LoginsUserWeekly (writer XLSXW_1)
LoginsUserWeekly (writer XLSXW_1)
    attributes: username auto(20), Full_Name auto(20), YearOfWeek auto(20), WeekStart datetime(20), WeekEnd datetime(20), LoginsPerWeek auto(20)
Note: Last login by user days ago
SQLCreator_2
    SQL_STATEMENT:
      SELECT distinct(username), format( max(Last_Login_Date), 'dd/MM/yyyy') as lastLogin,
      datediff(dd , max(Last_Login_Date), getdate()) as NumberofDayLastLogin
      FROM [SM_PREPRODPORTALUSAGELOGS]
      where [Environment]='$(GISServer)'
      group by username  ORDER BY NumberofDayLastLogin ASC
    MSSQL_ADO_QUERY_FEATURE_TYPES_FOR_MERGE_FILTERS = Yes
    EXPOSED_ATTRIBUTE_LIST = username,lastLogin,NumberofDayLastLogin
    MSSQL_ADO_COMMAND_TIMEOUT = 30
    MSSQL_ADO_NAMED_CONNECTION = AT MSSQL - REPORTS PREPROD
    DATASET = AT MSSQL - REPORTS PREPROD
    FORMAT = MSSQL_ADO
    RESULT -> LastLoginsByUserDaysAgo (writer XLSXW_1)
LastLoginsByUserDaysAgo (writer XLSXW_1)
    attributes: username auto(20), lastLogin datetime(20), NumberofDayLastLogin auto(20)

Bookmark: Logins Weekly
Note: Logins Weekly
SQLCreator_7
    SQL_STATEMENT:
      select datepart(week, Last_Login_Date) as YearOfWeek,
      dateadd (week, datepart(week, Last_Login_Date), dateadd (year, year(getdate())-1900, 0)) - 4 - datepart(dw, dateadd (week, datepart(week, Last_Login_Date), dateadd (year, year(getdate())-1900, 0)) - 4) + 1 as WeekStart,
      dateadd (week, datepart(week, Last_Login_Date), dateadd (year, year(getdate())-1900, 0)) - 4 - datepart(dw, dateadd (week, datepart(week, Last_Login_Date), dateadd (year, year(getdate())-1900, 0)) - 4) + 1 + 7  as WeekEnd,
      count(*) LoginsPerWeek from
      (
      SELECT distinct(username), Full_Name, Last_Login_Date
      FROM [SM_PREPRODPORTALUSAGELOGS] where
      Last_Login_Date between convert(date, '$(StartDate)', 112) and convert(date, '$(EndDate)', 112)
      and [Environment]='$(GISServer)'
      ) A
      group by datepart(week, Last_Login_Date)
      order by datepart(week, Last_Login_Date) desc
    MSSQL_ADO_QUERY_FEATURE_TYPES_FOR_MERGE_FILTERS = Yes
    EXPOSED_ATTRIBUTE_LIST = WeekStart,WeekEnd,YearOfWeek,LoginsPerWeek
    MSSQL_ADO_COMMAND_TIMEOUT = 30
    MSSQL_ADO_NAMED_CONNECTION = AT MSSQL - REPORTS PREPROD
    DATASET = AT MSSQL - REPORTS PREPROD
    FORMAT = MSSQL_ADO
    RESULT -> AttributeManager_4
AttributeManager_4
    ATTR_TABLE:
      SET_TO WeekStart = @DateTimeFormat(@Value(WeekStart),%d/%m/%Y)
      SET_TO WeekEnd = @DateTimeFormat(@Value(WeekEnd),%d/%m/%Y)
    -> LoginsWeekly (writer XLSXW_1)
LoginsWeekly (writer XLSXW_1)
    attributes: WeekStart auto(20), WeekEnd auto(20), YearOfWeek auto(20), LoginsPerWeek auto(20)

Bookmark: Weekly login Summary
Note: Weekly login Summary
SQLCreator_5
    SQL_STATEMENT:
      select Yow,
      dateadd (week, Yow, dateadd (year, year(getdate())-1900, 0)) - 4 - datepart(dw, dateadd (week, Yow, dateadd (year, year(getdate())-1900, 0)) - 4) + 1 as WeekStart,
      dateadd (week, Yow, dateadd (year, year(getdate())-1900, 0)) - 4 - datepart(dw, dateadd (week, Yow, dateadd (year, year(getdate())-1900, 0)) - 4) + 1 + 7  as WeekEnd,
      avg(TotalLogins) as AverageTotalLogins, sum(TotalLogins) as SumTotalLogins, ISNULL( STDEV(TotalLogins), 0) as StandardDeviationLogins from
      (
      select distinct(username), Full_Name, datepart(week, Last_Login_Date) Yow,  count(*) as TotalLogins from
      (
      SELECT distinct(username), Full_Name, Last_Login_Date
      FROM [SM_PREPRODPORTALUSAGELOGS] where
      Last_Login_Date between convert(date, '$(StartDate)', 112) and convert(date, '$(EndDate)', 112)
      and [Environment]='$(GISServer)'
      ) A
      group by username, Full_Name, datepart(week, Last_Login_Date)
      ) B
      group by Yow order by Yow desc
    MSSQL_ADO_QUERY_FEATURE_TYPES_FOR_MERGE_FILTERS = Yes
    EXPOSED_ATTRIBUTE_LIST = Yow,WeekStart,WeekEnd,AverageTotalLogins,SumTotalLogins,StandardDeviationLogins
    MSSQL_ADO_COMMAND_TIMEOUT = 30
    MSSQL_ADO_NAMED_CONNECTION = AT MSSQL - REPORTS PREPROD
    DATASET = AT MSSQL - REPORTS PREPROD
    FORMAT = MSSQL_ADO
    RESULT -> AttributeManager
AttributeManager
    ATTR_TABLE:
      SET_TO WeekStart = @DateTimeFormat(@Value(WeekStart),%d/%m/%Y)
      SET_TO WeekEnd = @DateTimeFormat(@Value(WeekEnd),%d/%m/%Y)
    -> WeeklyLoginsSummInfo (writer XLSXW_1)
WeeklyLoginsSummInfo (writer XLSXW_1)
    attributes: Yow auto(20), WeekStart datetime(20), WeekEnd datetime(20), AverageTotalLogins auto(20), SumTotalLogins auto(20), StandardDeviationLogins auto(20)

Bookmark: Weekly logins by Teams
Note: Weekly login by Teams
SQLCreator_6
    SQL_STATEMENT:
      select CurrentYear, Yow,
      dateadd (week, Yow, dateadd (year, year(getdate())-1900, 0)) - 4 - datepart(dw, dateadd (week, Yow, dateadd (year, year(getdate())-1900, 0)) - 4) + 1 as WeekStart,
      dateadd (week, Yow, dateadd (year, year(getdate())-1900, 0)) - 4 - datepart(dw, dateadd (week, Yow, dateadd (year, year(getdate())-1900, 0)) - 4) + 1 + 7  as WeekEnd,
      [Company_Area_Name], [Org_Unit_Name],  [Company_Division], [Company_Group], [Company_Department], [Company_Unit], [Company_Team], [Company_Subteam],
       TotalLogins from
      (
      select distinct([Org_Unit_Name]),
      [Company_Area_Name], [Company_Division], [Company_Group], [Company_Department], [Company_Unit], [Company_Team], [Company_Subteam] ,
      datepart(week, Last_Login_Date) Yow, datepart(year, Last_Login_Date) as CurrentYear, count(*) as TotalLogins from
      (
      SELECT distinct(username), Full_Name, Last_Login_Date,
      [Org_Unit_Name], [Company_Area_Name], [Company_Division], [Company_Group], [Company_Department], [Company_Unit], [Company_Team], [Company_Subteam]
      FROM [SM_PREPRODPORTALUSAGELOGS] where
      Last_Login_Date between convert(date, '$(StartDate)', 112) and convert(date, '$(EndDate)', 112)
      and [Environment]='$(GISServer)'
      ) A
      group by [Org_Unit_Name], [Company_Area_Name], [Company_Division], [Company_Group], [Company_Department], [Company_Unit], [Company_Team], [Company_Subteam] ,
       datepart(week, Last_Login_Date), datepart(year, Last_Login_Date)
       ) B
       order by CurrentYear , Yow desc
    MSSQL_ADO_QUERY_FEATURE_TYPES_FOR_MERGE_FILTERS = Yes
    EXPOSED_ATTRIBUTE_LIST = CurrentYear,Yow,WeekStart,WeekEnd,Company_Area_Name,Org_Unit_Name,Company_Division,Company_Group,Company_Department,Company_Unit,Company_Team,Company_Subteam,TotalLogins
    MSSQL_ADO_COMMAND_TIMEOUT = 30
    MSSQL_ADO_NAMED_CONNECTION = AT MSSQL - REPORTS PREPROD
    DATASET = AT MSSQL - REPORTS PREPROD
    FORMAT = MSSQL_ADO
    RESULT -> AttributeManager_3
AttributeManager_3
    ATTR_TABLE:
      SET_TO WeekStart = @DateTimeFormat(@Value(WeekStart),%d/%m/%Y)
      SET_TO WeekEnd = @DateTimeFormat(@Value(WeekEnd),%d/%m/%Y)
    -> WeeklyLoginByBU (writer XLSXW_1)
WeeklyLoginByBU (writer XLSXW_1)
    attributes: CurrentYear auto(20), Yow auto(20), WeekStart datetime(20), WeekEnd datetime(20), Company_Area_Name auto(20), Org_Unit_Name auto(20), Company_Division auto(20), Company_Group auto(20), Company_Department auto(20), Company_Unit auto(20), Company_Team auto(20), Company_Subteam auto(20), TotalLogins auto(20)

Bookmark: Unused users
Note: AT_OrgList [CSV2]
CSV (reader CSV2_1)
    attributes: /BIC/ZUSRID string, /BIC/ZPONAME string, ORGUNIT string, /BIC/ZORGUNIT string, /BIC/ZCURRORG string, COSTCENTER string, /BIC/ZCCTEXT string, /BIC/ZEMAIL string, EMPLGROUP string, EMPLGROUPTXT string, /BIC/ZZPOSLVL string, /BIC/ZZPOSLVLN string, CO_AREA string, /BIC/ZDIVISION string, /BIC/ZGROUP string, /BIC/ZDEPT string, /BIC/ZUNIT string, /BIC/ZTEAM string, /BIC/ZSUBTEAM string
    -> AttributeManager_5
Note: Format attributes
AttributeManager_5
    ATTR_TABLE:
      SET_TO /BIC/ZUSRID > User Id = @UpperCase(@Value(/BIC/ZUSRID))
      RENAME_SET_VALUE /BIC/ZPONAME > User_Designation
      RENAME_SET_VALUE ORGUNIT > Org_Unit
      RENAME_SET_VALUE /BIC/ZORGUNIT > Org_Unit_Name
      RENAME_SET_VALUE /BIC/ZCURRORG > Current_Organization
      RENAME_SET_VALUE COSTCENTER > Cost_Center
      RENAME_SET_VALUE /BIC/ZCCTEXT > Cost_Center_Name
      RENAME_SET_VALUE /BIC/ZEMAIL > User_Email
      RENAME_SET_VALUE EMPLGROUP > Employee_Group
      RENAME_SET_VALUE EMPLGROUPTXT > Employee_Group_Name
      RENAME_SET_VALUE /BIC/ZZPOSLVL > Employee_Level
      RENAME_SET_VALUE /BIC/ZZPOSLVLN > Employee_Level_Name
      RENAME_SET_VALUE CO_AREA > Company_Area_Name
      RENAME_SET_VALUE /BIC/ZDIVISION > Company_Division
      RENAME_SET_VALUE /BIC/ZGROUP > Company_Group
      RENAME_SET_VALUE /BIC/ZDEPT > Company_Department
      RENAME_SET_VALUE /BIC/ZUNIT > Company_Unit
      RENAME_SET_VALUE /BIC/ZTEAM > Company_Team
      RENAME_SET_VALUE /BIC/ZSUBTEAM > Company_Subteam
    -> FeatureMerger_2 [REQUESTOR]
Note: Get LastLogin by User
SQLCreator_8
    SQL_STATEMENT:
      select username, format(Last_Login_Date, 'dd/MM/yyyy') as LastLoginDate from
      (
      select distinct(username),  max(Last_Login_Date) as Last_Login_Date from [SM_PREPRODPORTALUSAGELOGS]
      where [Environment]='$(GISServer)'
      group by username
      ) as A ORDER BY Last_Login_Date DESC
    MSSQL_ADO_QUERY_FEATURE_TYPES_FOR_MERGE_FILTERS = Yes
    EXPOSED_ATTRIBUTE_LIST = username,LastLoginDate
    MSSQL_ADO_COMMAND_TIMEOUT = 30
    MSSQL_ADO_NAMED_CONNECTION = AT MSSQL - REPORTS PREPROD
    DATASET = AT MSSQL - REPORTS PREPROD
    FORMAT = MSSQL_ADO
    RESULT -> FeatureMerger_2 [SUPPLIER]
Note: Append OrgList attributes / Join on email, User_Email / Supplier First = Yes
FeatureMerger_2
    ATTR_ACCUM_MODE = Merge Supplier
    REJECT_NULL_MISSING_KEYS = No
    GEOM_TYPE = Build Polygons
    ATTR_CONFLICT_RES = Use Requestor
    MERGE_TYPE = Attributes Only
    IGNORE_NULLS = No
    PROCESS_DUPS = Yes
    CONNECT_Z_MODE = First Wins
    JOIN_KEYS = @UpperCase(@Value(/BIC/ZUSRID)) @UpperCase(@Value(username)) AUTO
    SUPPLIERS_FIRST = Yes
    UNMERGED_REQUESTOR -> Sorter
Sorter
    SORT_PARM = Company_Area_Name ALPHA ASCENDING Company_Division ALPHA ASCENDING Company_Group ALPHA ASCENDING Company_Department ALPHA ASCENDING Company_Unit ALPHA ASCENDING Company_Team ALPHA ASCENDING Company_Subteam ALPHA ASCENDING
    SORTED -> Unused users (writer XLSXW_1)
    SORTED -> AttributeKeeper
Unused users (writer XLSXW_1)
    attributes: User Id auto(20), User_Designation auto(20), Org_Unit auto(20), Org_Unit_Name auto(20), Current_Organization auto(20), Cost_Center auto(20), Cost_Center_Name auto(20), User_Email auto(20), Employee_Group auto(20), Employee_Group_Name auto(20), Employee_Level auto(20), Employee_Level_Name auto(20), Company_Area_Name auto(20), Company_Division auto(20), Company_Group auto(20), Company_Department auto(20), Company_Unit auto(20), Company_Team auto(20), Company_Subteam auto(20)
AttributeKeeper
    KEEP_ATTRS = Company_Group,Company_Subteam,User_Email,Company_Team,Company_Department,Company_Unit,Company_Area_Name,Company_Division
    -> Aggregator
Aggregator
    SEP = ,
    ORDERED = Yes
    GROUP_BY = Company_Group Company_Subteam Company_Team Company_Department Company_Unit Company_Area_Name Company_Division
    ACCUM_ATTRS_NAME = Merge Incoming Attributes
    COUNT_ATTR = User_Email
    MODE = Attributes Only
    AGGREGATE -> AttributeManager_7
AttributeManager_7
    ATTR_TABLE = RENAME_SET_VALUE User_Email > TotalCount
    -> UnusedUsersByDepartment (writer XLSXW_1)
UnusedUsersByDepartment (writer XLSXW_1)
    attributes: Company_Area_Name auto(20), Company_Division auto(20), Company_Group auto(20), Company_Department auto(20), Company_Unit auto(20), Company_Team auto(20), Company_Subteam auto(20), TotalCount auto(20)
