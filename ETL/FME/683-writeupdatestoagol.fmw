FME workspace 683-writeupdatestoagol.fmw

Parameters:
- ARCGISONLINEFEATURES_IN_USER_ARCGISONLINEFEATURES =   # User
- ARCGISONLINEFEATURES_IN_PASSWORD_ARCGISONLINEFEATURES =   # Password
- SourceDataset_XML = http://webservices.nextbus.com/service/publicXMLFeed?command=vehicleLocations&a=sf-muni&r=N&t=0   # Source XML File(s)

Readers:
- XML_1: XML from $(SourceDataset_XML) in LL84
- ARCGISONLINEFEATURES_1: ARCGISONLINEFEATURES from www.arcgis.com

Writers:
- ARCGISONLINEFEATURES_2: ARCGISONLINEFEATURES to www.arcgis.com

Bookmark: Readers
Note: New Bus information
vehicle (reader XML_1)
    attributes: vehicle.dirTag xml_char(7), vehicle.heading xml_decimal(4,0), vehicle.id xml_decimal(5,0), vehicle.lat xml_decimal(10,7), vehicle.leadingVehicleId xml_decimal(5,0), vehicle.lon xml_decimal(10,5), vehicle.predictable xml_char(6), vehicle.routeTag xml_char(2), vehicle.secsSinceReport xml_decimal(3,0), vehicle.speedKmHr xml_decimal(18,15), xml_fragment xml_xml, xml_id xml_char(16), xml_matched_element xml_char(8)
    -> BulkAttributeRenamer
Note: Read from existing ArcGIS / Online feature layer
Buses (reader ARCGISONLINEFEATURES_1)
    attributes: FID esriFieldTypeInteger, SECSSINCER esriFieldTypeDouble, ID esriFieldTypeDouble, ROUTETAG esriFieldTypeString(20), PREDICTABL esriFieldTypeString(20), SPEEDKMHR esriFieldTypeDouble, DIRTAG esriFieldTypeString(20), HEADING esriFieldTypeDouble
    -> UpdateDetector [input 1]

Bookmark: Modify XML feed to match feature layer data structure
BulkAttributeRenamer
    ATTRCHOICE = All Attributes
    PATTERN_ACTION_DISP = Remove Prefix String
    REPLACE_STR = vehicle.
    CASE_DISP = yes
    -> BulkAttributeRenamer_2
BulkAttributeRenamer_2
    ATTRCHOICE = All Attributes
    PATTERN_ACTION_DISP = Change Case
    CASE_CHANGE_TYPE = UPPERCASE
    -> VertexCreator
Note: Create point geometries / with current location
VertexCreator
    XVAL = @Value(LON)
    YVAL = @Value(LAT)
    MODE_NAME = Add Point
    -> UpdateDetector [input 2]

Bookmark: Check for Updates
Note: Adds FID attribute to features / that already exist in the Feature / Service.
UpdateDetector
    MATCH = NONE
    MATCHATTRS = HEADING LAT LON
    EXTRA_VERTEX_TOLERANCE = 0
    LENIENT_MATCH = no
    BLANK_AND_MISSING_DIFFER = No
    KEYATTR = ID
    Updated -> AttributeCreator
    Inserted -> AttributeCreator_2
    Deleted -> AttributeCreator_3

Bookmark: Set writer action
Note: Tag as UPDATE
AttributeCreator
    ATTR_LIST = fme_db_operation,UPDATE
    -> Buses (writer ARCGISONLINEFEATURES_2)
Note: Tag as INSERT
AttributeCreator_2
    ATTR_LIST = fme_db_operation,INSERT
    -> Buses (writer ARCGISONLINEFEATURES_2)
Note: Tag as DELETE
AttributeCreator_3
    ATTR_LIST = fme_db_operation,DELETE
    -> Buses (writer ARCGISONLINEFEATURES_2)

Bookmark: ArcGIS Online Feature Writer
  This writer is in update mode, so will check the FID on each of the features
  sent here and will update, insert or delete the corresponding one in the existing layer
Buses (writer ARCGISONLINEFEATURES_2)
    attributes: FID esriFieldTypeInteger, SECSSINCER esriFieldTypeDouble, ID esriFieldTypeDouble, ROUTETAG esriFieldTypeString(20), PREDICTABL esriFieldTypeString(20), SPEEDKMHR esriFieldTypeDouble, DIRTAG esriFieldTypeString(20), HEADING esriFieldTypeDouble

FME custom transformer UpdateDetector
This transformer is based on ChangeDetector extending its functionality by adding Updated output port. It detects changes between two sets of input features.
One set of features enters the transformer via the Original port. The other set enters via the Revised port. Both sets must have a key attribute, which will be used to compare them against each other.
An Original feature is output via the Unchanged port when it is found to have matching key attribute and either matching geometry, matching attribute values, or both, with a feature in the Revised set.
An Original feature is output via the Deleted port when no key attribute match for it can be found in the Revised set.
A Revised feature with no key attribute match in the Original set is output via the Inserted port.
A Revised feature with key attribute match in the Original set and has changes either in geometry, or attribute values, or both, is output via the Updated port.
Inserted, updated and deleted features will have fme_db_operation set to INSERT, UPDATE or DELETE respectively.
Please note that to get correct results, the key attribute must be provided to both "Key Attribute" and "Attribute(s) to match" parameter prompts. 
Connect the transformer in your workspace and set the required parameters.
If Lenient Geometry Matching is set to yes then the order of points in line and area features will be ignored.
If Treat Blank Value as Different From Missing Attribute is Yes, then an attribute will be considered different for two features when one feature contains the attribute with a blank value and the other feature does not contain the attribute at all.
When geometry is being matched, Extra Vertex Tolerance can allow for extra vertices along line segments. A value of 0 means that no such extra vertices are permitted. A nonzero value controls how close any extra vertices must be to the line connecting the adjoining matching vertices. Note: This setting has no effect when using lenient geometry matching.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- KEYATTR =   # " " Key Attribute
- MATCH = 2D   # Match Geometry
- LENIENT_MATCH = no   # Lenient Geometry Matching
- MATCHATTRS =   # " " Attribute(s) to match
- BLANK_AND_MISSING_DIFFER = No   # Treat Blank Value as Different From Missing Attribute
- EXTRA_VERTEX_TOLERANCE = 0   # Extra Vertex Tolerance (optional)

Original (input)
    -> ATTRIBUTECREATOR
Note: Created by Dmitri Bagh / February 03, 2006 / dmitri.bagh@safe.com
Revised (input)
    -> ATTRIBUTECREATOR_2
Note: All parameters / are published / to match functionality / of ChangeDetector
Note: UPDATEDETECTOR
ChangeDetector
    MATCH = $(MATCH)
    MATCHATTRS = $(MATCHATTRS)
    EXTRA_VERTEX_TOLERANCE = $(EXTRA_VERTEX_TOLERANCE)
    LENIENT_MATCH = $(LENIENT_MATCH)
    MATCH_STRATEGY = Match Selected Attributes
    BLANK_AND_MISSING_DIFFER = $(BLANK_AND_MISSING_DIFFER)
    UNCHANGED -> ATTRIBUTEREMOVER_3
    DELETED -> Matcher
    ADDED -> Matcher_2
Updated (output)
Inserted (output)
Unchanged (output)
Deleted (output)

Bookmark: OrigFlag Creators
  Assigning OrigFlag Y for original 
  features and N for revised.
  For further use in testers 
  after Matcher 
  where original and revised 
  feaures can be merged together.
ATTRIBUTECREATOR: AttributeCreator
    ATTR_LIST = OrigFlag,Y
    -> ChangeDetector [input 1]
    -> Matcher_2
ATTRIBUTECREATOR_2: AttributeCreator
    ATTR_LIST = OrigFlag,N
    -> ChangeDetector [input 2]
    -> Matcher

Bookmark: Matchers
  Here published Key Attribute
  distinguishes between added 
  and modified (above), 
  and - between deleted 
  and modified (below)
Matcher_2
    BLANK_AND_MISSING_DIFFER_DISP = As Missing Attribute
    MATCH = NONE
    MATCHATTRS = $(KEYATTR)
    LENIENT_MATCH = No
    MATCH_STRATEGY = Match Selected Attributes
    CNT_ATTR = _match_id
    DIFFATTRS = OrigFlag
    NOT_MATCHED -> TESTER_2
    MATCHED -> TESTER
Matcher
    BLANK_AND_MISSING_DIFFER_DISP = As Missing Attribute
    MATCH = NONE
    MATCHATTRS = $(KEYATTR)
    LENIENT_MATCH = No
    MATCH_STRATEGY = Match Selected Attributes
    CNT_ATTR = _match_id
    DIFFATTRS = OrigFlag
    NOT_MATCHED -> TESTER_3

Bookmark: Testers
  For updated and added 
  we keep revised features
  For deleted - original features
TESTER: Tester
    TEST_MODE = Automatic
    TEST_CLAUSE = TEST @Value(OrigFlag) = N
    BOOL_OP = OR
    TEST_LIST = &OrigFlag,=,N
    PASSED -> ATTRIBUTEREMOVER
TESTER_2: Tester
    TEST_MODE = Automatic
    TEST_CLAUSE = TEST @Value(OrigFlag) = N
    BOOL_OP = OR
    TEST_LIST = &OrigFlag,=,N
    PASSED -> ATTRIBUTEREMOVER_2
TESTER_3: Tester
    TEST_MODE = Automatic
    TEST_CLAUSE = TEST @Value(OrigFlag) = Y
    BOOL_OP = OR
    TEST_LIST = &OrigFlag,=,Y
    PASSED -> ATTRIBUTEREMOVER_4

Bookmark: Deleting temp attributes
ATTRIBUTEREMOVER: AttributeRemover
    REMOVE_ATTRS = _match_id,OrigFlag
    -> AttributeCreator
ATTRIBUTEREMOVER_2: AttributeRemover
    REMOVE_ATTRS = _match_id,OrigFlag
    -> AttributeCreator_2
ATTRIBUTEREMOVER_3: AttributeRemover
    REMOVE_ATTRS = OrigFlag
    -> Unchanged (output)
ATTRIBUTEREMOVER_4: AttributeRemover
    REMOVE_ATTRS = _match_id,OrigFlag
    -> AttributeCreator_3

Bookmark: Add fme_db_operation attribute
AttributeCreator
    ATTR_LIST = fme_db_operation,UPDATE
    -> Updated (output)
AttributeCreator_2
    ATTR_LIST = fme_db_operation,INSERT
    -> Inserted (output)
AttributeCreator_3
    ATTR_LIST = fme_db_operation,DELETE
    -> Deleted (output)
